FME workspace zad12_wariant_a.fmw

Parameters:
- SourceDataset_SHAPEFILE = $(FME_MF_DIR)dane\T2018_KAR_POI_TABLE.shp   # Source Esri Shapefile(s)
- SourceDataset_SHAPEFILE_5 = $(FME_MF_DIR)dane\T2018_KAR_STREET_NODE.shp   # Source Esri Shapefile(s)
- SourceDataset_SHAPEFILE_4 = $(FME_MF_DIR)dane\T2018_KAR_STREETS.shp   # Source Esri Shapefile(s)
- SourceDataset_CSV2 = $(FME_MF_DIR)dane\trasa_pk.csv   # Source CSV (Comma Separated Value) File(s)
- DestDataset_GEODATABASE_FILE_3 = $(FME_MF_DIR)bez_kosztów.gdb   # File Geodatabase

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_4)
- CSV2_1: CSV2 from $(SourceDataset_CSV2)

Writers:
- GEODATABASE_FILE_2: GEODATABASE_FILE to $(DestDataset_GEODATABASE_FILE_3)

T2018_KAR_POI_TABLE (reader SHAPEFILE_1)
    attributes: POI_ID long, LINK_ID long, TYPE varchar(250), POI_NAME varchar(250), ST_NAME varchar(250), LAT number(31,15), LON number(31,15)
    -> Reprojector_4
Reprojector_4
    DEST = EPSG:3068
    INTERPOLATION_TYPE = NearestNeighbor
    RASTER_CELL_SIZE = PreserveCells
    RASTER_TOLERANCE = 0.0
    REPROJECTED -> Clipper_2 [CANDIDATE]
T2018_KAR_STREET_NODE (reader SHAPEFILE_2)
    attributes: NODE_ID long, LINK_ID long, POINT_NUM long, Z_LEVEL long, INTERSECT varchar(1), LAT number(31,15), LON number(31,15)
    -> Reprojector
Reprojector
    DEST = EPSG:3068
    INTERPOLATION_TYPE = NearestNeighbor
    RASTER_CELL_SIZE = PreserveCells
    RASTER_TOLERANCE = 0.0
    REPROJECTED -> SpatialFilter [Candidate]
T2018_KAR_STREETS (reader SHAPEFILE_3)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_3
    -> AnchoredSnapper [ANCHOR]
Reprojector_3
    DEST = EPSG:3068
    INTERPOLATION_TYPE = NearestNeighbor
    RASTER_CELL_SIZE = PreserveCells
    RASTER_TOLERANCE = 0.0
    REPROJECTED -> ShortestPathFinder [NETWORK]
CSV (reader CSV2_1)
    attributes: id uint32, x real32, y real32
    -> VertexCreator
VertexCreator
    COORDSYS = LL-WGS84
    MEASURE_TYPE_LOOKUP = CONTINUOUS
    MODE = REPLACE
    REMOVE_ATTRIBUTES = No
    XVAL = @Value(x)
    YVAL = @Value(y)
    MEASURE_TYPE = Continuous
    MODE_NAME = Replace with Point
    -> AnchoredSnapper [CANDIDATE]
AnchoredSnapper
    EXTEND_LINES = NEVER
    SNAPTYPE = END_NODE
    SNAP_3D = No
    TOLERANCE = 50
    SNAPPED -> LineBuilder
LineBuilder
    ACCUM_INPUT_ATTRS_LOOKUP = One
    REMOVE_DUPLICATES_LOOKUP = NO
    ACCUM_INPUT_ATTRS = Use Attributes From One Feature
    REMOVE_DUPLICATES = No
    LINE -> Reprojector_2
Reprojector_2
    DEST = EPSG:3068
    INTERPOLATION_TYPE = NearestNeighbor
    RASTER_CELL_SIZE = PreserveCells
    RASTER_TOLERANCE = 0.0
    REPROJECTED -> ShortestPathFinder [FROM-TO]
ShortestPathFinder
    ALLOW_UTURNS = Yes
    REORDER_MODE = NONE
    SNAP_POINTS = No
    THREE_D = No
    WEIGHT_ATTR_CHOICE = BY_LENGTH
    PATH -> Bufferer_2
    PATH -> SpatialFilter [Filter]
    PATH -> LengthCalculator_2
Bufferer_2
    ANGLE = 22.5
    CAP_STYLE_LOOKUP = CAP_ARC
    CORNER_STYLE_LOOKUP = JOIN_ARC
    MODE = AREA
    OFFSET = 5
    OFFSET_UNITS = NONE
    PRECISION = APPROX
    CAP_STYLE = Arc
    CORNER_STYLE = Arc
    BUFFERED -> Clipper_2 [CLIPPER]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> writer_gjson [Inside]
writer_gjson: FeatureWriter
    CONFIG_PARAMETERS = ESCAPE_COMMAS_IN_FTP_FORMAT_PARAMETERS,no
    DATASET = $(FME_MF_DIR_ENCODED)bez_kosztow.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    GEOJSON_WRITE_FEATURE_IDS = Yes
    GEOJSON_WRITE_NESTED = YES
    TOTAL_FEATURES_WRITTEN_ATTR = _total_features_written
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> wariant_a (writer GEODATABASE_FILE_2)
LengthCalculator_2
    DIM = 2
    LEN_ATTR = _length
    MULT = 1
    -> wariant_a (writer GEODATABASE_FILE_2)
wariant_a (writer GEODATABASE_FILE_2)
    attributes: id double, x float, y float, _total_cost char(2048), NODE_ID integer, LINK_ID integer, POINT_NUM integer, Z_LEVEL integer, INTERSECT char(1), LAT double(31,15), LON double(31,15), _predicate char(2048), _length double
