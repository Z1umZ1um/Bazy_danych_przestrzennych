FME workspace cwiczenia9_10.fmw

Parameters:
- SourceDataset_GEOTIFF = ""$(FME_MF_DIR)ras250_gb\data\HP.tif" "$(FME_MF_DIR)ras250_gb\data\HT.tif" "$(FME_MF_DIR)ras250_gb\data\HU.tif" "$(FME_MF_DIR)ras250_gb\data\HW.tif" "$(FME_MF_DIR)ras250_gb\data\HX.tif" "$(FME_MF_DIR)ras250_gb\data\HY.tif" "$(FME_MF_DIR)ras250_gb\data\HZ.tif" "$(FME_MF_DIR)ras250_gb\data\NA.tif" "$(FME_MF_DIR)ras250_gb\data\NB.tif" "$(FME_MF_DIR)ras250_gb\data\NC.tif" "$(FME_MF_DIR)ras250_gb\data\ND.tif" "$(FME_MF_DIR)ras250_gb\data\NF.tif" "$(FME_MF_DIR)ras250_gb\data\NG.tif" "$(FME_MF_DIR)ras250_gb\data\NH.tif" "$(FME_MF_DIR)ras250_gb\data\NJ.tif" "$(FME_MF_DIR)ras250_gb\data\NK.tif" "$(FME_MF_DIR)ras250_gb\data\NL.tif" "$(FME_MF_DIR)ras250_gb\data\NM.tif" "$(FME_MF_DIR)ras250_gb\data\NN.tif" "$(FME_MF_DIR)ras250_gb\data\NO.tif" "$(FME_MF_DIR)ras250_gb\data\NR.tif" "$(FME_MF_DIR)ras250_gb\data\NS.tif" "$(FME_MF_DIR)ras250_gb\data\NT.tif" "$(FME_MF_DIR)ras250_gb\data\NU.tif" "$(FME_MF_DIR)ras250_gb\data\NW.tif" "$(FME_MF_DIR)ras250_gb\data\NX.tif" "$(FME_MF_DIR)ras250_gb\data\NY.tif" "$(FME_MF_DIR)ras250_gb\data\NZ.tif" "$(FME_MF_DIR)ras250_gb\data\OV.tif" "$(FME_MF_DIR)ras250_gb\data\SC.tif" "$(FME_MF_DIR)ras250_gb\data\SD.tif" "$(FME_MF_DIR)ras250_gb\data\SE.tif" "$(FME_MF_DIR)ras250_gb\data\SH.tif" "$(FME_MF_DIR)ras250_gb\data\SJ.tif" "$(FME_MF_DIR)ras250_gb\data\SK.tif" "$(FME_MF_DIR)ras250_gb\data\SM.tif" "$(FME_MF_DIR)ras250_gb\data\SN.tif" "$(FME_MF_DIR)ras250_gb\data\SO.tif" "$(FME_MF_DIR)ras250_gb\data\SP.tif" "$(FME_MF_DIR)ras250_gb\data\SR.tif" "$(FME_MF_DIR)ras250_gb\data\SS.tif" "$(FME_MF_DIR)ras250_gb\data\ST.tif" "$(FME_MF_DIR)ras250_gb\data\SU.tif" "$(FME_MF_DIR)ras250_gb\data\SV.tif" "$(FME_MF_DIR)ras250_gb\data\SW.tif" "$(FME_MF_DIR)ras250_gb\data\SX.tif" "$(FME_MF_DIR)ras250_gb\data\SY.tif" "$(FME_MF_DIR)ras250_gb\data\SZ.tif" "$(FME_MF_DIR)ras250_gb\data\TA.tif" "$(FME_MF_DIR)ras250_gb\data\TF.tif" "$(FME_MF_DIR)ras250_gb\data\TG.tif" "$(FME_MF_DIR)ras250_gb\data\TL.tif" "$(FME_MF_DIR)ras250_gb\data\TM.tif" "$(FME_MF_DIR)ras250_gb\data\TQ.tif" "$(FME_MF_DIR)ras250_gb\data\TR.tif" "$(FME_MF_DIR)ras250_gb\data\TV.tif""   # Source GeoTIFF File(s) or URL(s)
- SourceDataset_OGCGEOPACKAGE = $(FME_MF_DIR)bdline_gpkg_gb\Data\bdline_gb.gpkg   # GeoPackage File
- DestDataset_POSTGIS_RASTER = cw9_test   # Connection

Readers:
- GEOTIFF_1: GEOTIFF from $(SourceDataset_GEOTIFF)
- OGCGEOPACKAGE_1: OGCGEOPACKAGE from $(SourceDataset_OGCGEOPACKAGE)

Writers:
- POSTGIS_RASTER_1: POSTGIS_RASTER to $(DestDataset_POSTGIS_RASTER)

scotland_and_wales_const (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> Tester
Tester
    BOOL_OP = OR
    TEST_CLAUSE = CASE_INSENSITIVE_TEST @Value(File_Name) BEGINS_WITH SOUTH_WALES
    TEST_MODE = TEST
    PASSED -> SpatialFilter [Filter]
    PASSED -> Dissolver
Dissolver
    ACCUM_INPUT_ATTRS_LOOKUP = One
    CLEANING_TOLERANCE_LOOKUP = AUTO
    CONNECT_Z_MODE_LOOKUP = FIRST_WINS
    DEAGGREGATE_INPUT = Yes
    ACCUM_INPUT_ATTRS = Use Attributes From One Feature
    CLEANING_TOLERANCE = Automatic
    CONNECT_Z_MODE = First Wins
    AREA -> RasterGCPClipper [CLIPPER]
GEOTIFF (reader GEOTIFF_1)
    -> Reprojector
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> RasterMosaicker
RasterMosaicker
    ACCUM_ATTRS = ONE
    INTERPOLATION_TYPE = NearestNeighbor
    MERGE_PALETTES_NAME = Yes
    NODATA_OVERWRITE = No
    OVERLAPPING_VALUES = last
    SNAPPING_TYPE = RESAMPLE
    ACCUM_ATTRS_NAME = Use Attributes From One Feature
    INTERPOLATION_TYPE_NAME = Nearest Neighbor
    MERGE_PALETTES = Yes
    SNAPPING_TYPE_NAME = Resample
    -> RasterGCPClipper [RASTER]
RasterGCPClipper
    EXTENTS = No
    UNITS = Ground
    CLIPPED_INSIDE -> RasterPaletteResolver
RasterPaletteResolver
    -> exports (writer POSTGIS_RASTER_1)
exports (writer POSTGIS_RASTER_1)
    attributes: name text, area_code text, area_description text, file_name text, feature_serial_number int4, collection_serial_number int4, global_polygon_id int4, admin_unit_id int4, census_code text, hectares float8, non_inland_area float8, area_type_code text, area_type_description text, non_area_type_code text, non_area_type_description text, _predicate varchar
Reprojector
    DEST = EPSG:4326
    INTERPOLATION_TYPE = NearestNeighbor
    RASTER_CELL_SIZE = PreserveCells
    RASTER_TOLERANCE = 0.0
    SOURCE = EPSG:27700
    REPROJECTED -> BoundingBoxReplacer
    REPROJECTED -> RasterPropertyExtractor
RasterPropertyExtractor
    -> AttributeCreator1
AttributeCreator1
    ATTR_TABLE = SET_TO extent_size (varchar(200)) = (@Value(_max_x) - @Value(_min_x)) * (@Value(_max_y) - @Value(_min_y))
    INPUT_PORT_CONNECTED = CONNECTED
    -> AttributeCreator
AttributeCreator
    ATTR_TABLE = SET_TO NewName (varchar(200)) = @Value(fme_basename)_@Value(extent_size)
    INPUT_PORT_CONNECTED = CONNECTED
BoundingBoxReplacer
    BBTYPE = BB
    BOXTYPE = 2D Bounding Box

FME custom transformer RasterGCPClipper
Clips Rasters while retaining the Ground Control Point (GCP) georeferencing.
The RasterGCPClipper can be used in place of a standard Clipper. Non-raster features will be discarded. Rasters without GCPs will be clipped as in the regular Clipper. Rasters that are completely inside or outside the clipping boundary will retain their original GCPs. Rasters that are clipped will have a new set of GCPs created to represent the new raster boundaries.
The transformer takes two parameters:
Clipper in Ground or Pixel Coordinates - If Ground is chosen, the transformer will use the image GCPs to adjust these coordinates to pixel coordinates before clipping. Most raster formats have pixel 0,0 at the top left, so the Y coordinates should be less than 0.
Preserve Clippee Extents - If this parameter is set to No, the CLIPPED_INSIDE rasters will be equal to the intersections of the clippers and clippees. Otherwise, the intersections will be padded by nodata so that the extents are identical to those of the input rasters. Setting this to No will result in new GCPs being created to represent the new raster boundaries.

Parameters:
- EXTENTS = No   # Preserve Clippee Extents
- UNITS = Ground   # Clipper in Ground or Pixel coordinates

CLIPPER (input)
    -> GeometryExtractor
Note: Extract clipper geometry
GeometryExtractor
    ATTR = _geometry
    KIND = fmebinary
    KIND_LONG = FME Binary
    -> AttributeCreator
Note: Create join attributes
AttributeCreator
    ATTR_LIST = _RasterGCPClipper_join,0
    -> FeatureMerger [SUPPLIER]
RASTER (input)
    -> Counter
Note: Set raster id
Counter
    CNT_ATTR = _RasterGCPClipper_groupby
    DOMAIN = counter
    SCOPE = Local
    START = 0
    SCOPEVAR = Local
    -> AttributeCreator_2
    -> AttributeCreator_4
AttributeCreator_2
    ATTR_LIST = _RasterGCPClipper_join,0
    -> FeatureMerger [REQUESTOR]
Note: Join clipper to raster to / create a clipper for each raster
FeatureMerger
    BUILD_INCOMPLETE = No
    LIST_NAME = _RasterGCPClipper_Clipper_list
    PROCESS_DUPS = No
    REFEEATTR = _RasterGCPClipper_join
    REFERATTR = _RasterGCPClipper_join
    REFERENCE_INFO = ATTRIBUTES
    MERGE_TYPE = Attributes Only
    COMPLETE -> ListExploder
Note: In case there more than / one clippers in use
ListExploder
    ATTR_MODE = LEAN
    INDEX_ATTR = _element_index
    LIST_ATTR = _RasterGCPClipper_Clipper_list{}
    MODE = List Elements and Original Attributes
    LIST_FOUND -> GeometryReplacer
Note: Replace raster / geometry with clipper
GeometryReplacer
    ATTR = _geometry
    KIND = fmebinary
    KIND_LONG = FME Binary
    -> AttributeCreator_3
AttributeCreator_3
    ATTR_LIST = _RasterClipper_geomtype,clipper
    -> StringConcatenator
Note: Set input type
AttributeCreator_4
    ATTR_LIST = _RasterClipper_geomtype,raster
    -> StringConcatenator
Note: Concatenate input parameters
StringConcatenator
    PARM_LINE = fme_basicstring:8%1%10:$(UNITS)_$(EXTENTS)
    VAL_ATTR = _RasterGCPClipper_route
    -> AttributeFilter
Note: Route to unique / parameter choice sets
AttributeFilter
    ATTR_NAME = _RasterGCPClipper_route
    ATTR_VALUES = <BLANK>,<UNFILTERED>,Ground_Yes,Ground_No,Pixel_Yes,Pixel_No
    Ground_Yes -> AttributeFilter_2
    Ground_No -> AttributeFilter_3
    Pixel_Yes -> AttributeFilter_4
    Pixel_No -> AttributeFilter_5
Note: Separate clipper from raster
AttributeFilter_2
    ATTR_NAME = _RasterClipper_geomtype
    ATTR_VALUES = <BLANK>,<UNFILTERED>,clipper,raster
    clipper -> DoTheClip_5 [CLIPPER]
    raster -> DoTheClip_5 [RASTER]
Note: Clip using group by to ensure / that each clipper is warped to / the proper pixel boundaries
DoTheClip_5
    CT = Ground
    GB = _RasterGCPClipper_groupby
    PCE = Yes
    INSIDE -> AttributeRemover_2
    CLIPPED_INSIDE -> AttributeRemover_4
    CLIPPED_OUTSIDE -> AttributeRemover_3
    OUTSIDE -> AttributeRemover
AttributeFilter_3
    ATTR_NAME = _RasterClipper_geomtype
    ATTR_VALUES = <BLANK>,<UNFILTERED>,clipper,raster
    clipper -> DoTheClip_2 [CLIPPER]
    raster -> DoTheClip_2 [RASTER]
DoTheClip_2
    CT = Ground
    GB = _RasterGCPClipper_groupby
    PCE = No
    INSIDE -> AttributeRemover_2
    CLIPPED_INSIDE -> AttributeRemover_4
    CLIPPED_OUTSIDE -> AttributeRemover_3
    OUTSIDE -> AttributeRemover
AttributeFilter_4
    ATTR_NAME = _RasterClipper_geomtype
    ATTR_VALUES = <BLANK>,<UNFILTERED>,clipper,raster
    clipper -> DoTheClip_3 [CLIPPER]
    raster -> DoTheClip_3 [RASTER]
DoTheClip_3
    CT = Pixel
    GB = _RasterGCPClipper_groupby
    PCE = Yes
    INSIDE -> AttributeRemover_2
    CLIPPED_INSIDE -> AttributeRemover_4
    CLIPPED_OUTSIDE -> AttributeRemover_3
    OUTSIDE -> AttributeRemover
AttributeFilter_5
    ATTR_NAME = _RasterClipper_geomtype
    ATTR_VALUES = <BLANK>,<UNFILTERED>,clipper,raster
    clipper -> DoTheClip_4 [CLIPPER]
    raster -> DoTheClip_4 [RASTER]
DoTheClip_4
    CT = Pixel
    GB = _RasterGCPClipper_groupby
    PCE = No
    INSIDE -> AttributeRemover_2
    CLIPPED_INSIDE -> AttributeRemover_4
    CLIPPED_OUTSIDE -> AttributeRemover_3
    OUTSIDE -> AttributeRemover
AttributeRemover_2
    REMOVE_ATTRS = _RasterGCPClipper_groupby,_RasterClipper_geomtype,_RasterGCPClipper_join,_geometry,_element_index,_RasterGCPClipper_route
    -> INSIDE (output)
INSIDE (output)
AttributeRemover_4
    REMOVE_ATTRS = _RasterGCPClipper_groupby,_RasterClipper_geomtype,_RasterGCPClipper_join,_geometry,_element_index,_RasterGCPClipper_route
    -> CLIPPED_INSIDE (output)
CLIPPED_INSIDE (output)
AttributeRemover_3
    REMOVE_ATTRS = _RasterGCPClipper_groupby,_RasterClipper_geomtype,_RasterGCPClipper_join,_geometry,_element_index,_RasterGCPClipper_route
    -> CLIPPED_OUTSIDE (output)
CLIPPED_OUTSIDE (output)
AttributeRemover
    REMOVE_ATTRS = _RasterGCPClipper_groupby,_RasterClipper_geomtype,_RasterGCPClipper_join,_geometry,_element_index,_RasterGCPClipper_route
    -> OUTSIDE (output)
OUTSIDE (output)

FME custom transformer DoTheClip

Parameters:
- CT = Ground   # Clipper in Ground or Pixel Coordinates
- PCE = No   # Preserve Clippee Extents
- GB =   # " " Group By

RASTER (input)
    -> VariableSetter
Note: Set raster flag
VariableSetter
    SCOPE = Local
    VALUE = Yes
    VARNAME = GCPRaster
    -> Counter
Note: Create unique / id for each input
Counter
    CNT_ATTR = _RasterGCPClipperID
    DOMAIN = counter
    SCOPE = Local
    START = 0
    SCOPEVAR = Local
    -> GeometryFilter
Note: Filter out non-raster features
GeometryFilter
    BREAK_AGG = No
    RASTER -> RasterGCPExtractor_2
Note: Extract original GCPs
RasterGCPExtractor_2
    -> NullAttributeReplacer
    -> Clipper [CLIPPEE]
Note: Replace null GCP / with 1:1 transform
NullAttributeReplacer
    NEW_VALUE = 0 0 0 0 0;0 1 0 -1 0;1 1 1 -1 0;1 0 1 0 0
    SRC_ATTRS = _gcp_value
    -> RasterPropertiesExtractor
CLIPPER (input)
    -> Tester_6
Note: Test for Pixel or / Ground coordinates
Tester_6
    BOOL_OP = OR
    TEST_CLAUSE = TEST "$(CT)" = "Pixel"
    TEST_MODE = Automatic
    PASSED -> Clipper [CLIPPER]
    FAILED -> AffineWarper_2 [OBSERVED]
Note: Warp boundary to pixel / space by GCP vectors
AffineWarper_2
    CORRECTED -> BoundingBoxReplacer
Note: Replace warped boundary / with bounding box
BoundingBoxReplacer
    BBTYPE = BB
    BOXTYPE = Bounding Box
    BOX -> Clipper [CLIPPER]
Note: Raster changed?
Tester
    BOOL_OP = OR
    TEST_CLAUSE = TEST "$(PCE)" = "No"
    TEST_MODE = Automatic
    PASSED -> Tester_3
    FAILED -> Tester_4
Note: Skip rasters / with no GCPs
Tester_4
    BOOL_OP = OR
    TEST_CLAUSE = TEST "@Value(_gcp_value)" = ""
    TEST_MODE = Automatic
    PASSED -> Cloner_2
    FAILED -> RasterGCPSetter_3
Note: Replace GCPs on raster
RasterGCPSetter_3
    GCP_VALUE = @Value(_gcp_value)
    SOURCE = &_gcp_coordsys
    -> Cloner_2
Note: Skip rasters / with no GCPs
Tester_3
    BOOL_OP = OR
    TEST_CLAUSE = TEST "@Value(_gcp_value)" = ""
    TEST_MODE = Automatic
    PASSED -> Cloner_2
    FAILED -> RasterPropertiesExtractor_2
    FAILED -> BoundingBoxReplacer_2
Cloner_2
    COPIES = 1
    COPYATT = _copynum
    COPY -> Cloner_3
Cloner_3
    COPIES = 1
    COPYATT = _copynum
    COPY -> AttributeFilter
Note: Get raster bounds
RasterPropertiesExtractor_2
    -> RasterGeoreferencer
Note: Force raster origin to 0,0
RasterGeoreferencer
    POINTANDANGLE_OR_EXTENTS = PointAndAngle
    ROTATION = 0.0
    X_SPACING = 1
    X_UL_COORD = 0
    Y_SPACING = 1
    Y_UL_COORD = 0
    -> FeatureMerger [REQUESTOR]
    -> BoundingBoxReplacer_3
CLIPPED_OUTSIDE (output)
OUTSIDE (output)

Bookmark: Interpret GCPs into Affine control vectors
Note: Get bounds
RasterPropertiesExtractor
    -> AttributeSplitter
Note: Split GCP coordinate entries
AttributeSplitter
    ATTR_NAME = _gcp_value
    DELIMITER = ;
    DROP_EMPTY_PARTS = No
    LIST_NAME = _gcps
    TRIM_COMMAND = trim
    TRIM_OPTION = Both
    -> ListExploder
Note: Explode list of GCP entries
ListExploder
    ATTR_MODE = LEAN
    INDEX_ATTR = _element_index
    LIST_ATTR = _gcps{}
    MODE = List Elements and Original Attributes
    LIST_FOUND -> AttributeSplitter_2
Note: Split GCP coordinates
AttributeSplitter_2
    ATTR_NAME = _gcps
    DELIMITER = " "
    DROP_EMPTY_PARTS = No
    LIST_NAME = _coords
    TRIM_COMMAND = trim
    TRIM_OPTION = Both
    -> 2DPointReplacer
Note: Create GCP vector
2DPointReplacer
    XVALATTR = @Value(_coords{2})
    YVALATTR = @Value(_coords{3})
    POINT -> 2DPointAdder
2DPointAdder
    XVALATTR = @Value(_coords{0})
    YVALATTR = -@Value(_coords{1})
    -> AffineWarper_2 [CONTROL]
    -> Orientor

Bookmark: Dummy transform to prevent error when raster missing
Note: Create dummy vectors / to avoid error
Creator
    GEOM = <?xml version="1.0" encoding="US_ASCII" standalone="no" ?><geometry><line><coord x="0" y="0"/><coord x="1" y="1"/></line></geometry>
    GEOMTYPE = Geometry Object
    NUM = 1
    CREATED -> AttributeCreator_9
AttributeCreator_9
    ATTR_LIST = _go,No
    -> VariableRetriever
Note: Get raster flag
VariableRetriever
    SCOPE = Local
    VALUE_ATTR = _go
    VARNAME = GCPRaster
    -> AttributeCreator_5
    -> AttributeCreator_6
    -> AttributeCreator_7
    -> AttributeCreator_8
Note: Create coordinates
AttributeCreator_5
    ATTR_LIST = _coords{0},0,_coords{1},0,_coords{2},1,_coords{3},1
    -> Tester_7
AttributeCreator_6
    ATTR_LIST = _coords{0},0,_coords{1},1,_coords{2},1,_coords{3},2
    -> Tester_7
AttributeCreator_7
    ATTR_LIST = _coords{0},1,_coords{1},1,_coords{2},2,_coords{3},2
    -> Tester_7
AttributeCreator_8
    ATTR_LIST = _coords{0},1,_coords{1},0,_coords{2},2,_coords{3},1
    -> Tester_7
Note: Continue only if rasters missing
Tester_7
    BOOL_OP = OR
    TEST_CLAUSE = TEST "@Value(_go)" = "Yes"
    TEST_MODE = Automatic
    FAILED -> 2DPointReplacer

Bookmark: Extract new GCP ground coordinates
Note: Reverse vector
Orientor
    KIND = REVERSE
    ORIENTED -> AffineWarper [CONTROL]
Note: Extract clipped bounds
BoundingBoxReplacer_2
    BBTYPE = BB
    BOXTYPE = Bounding Box
    BOX -> AffineWarper [OBSERVED]
Note: Warp clipped bounds to / ground space by GCP vectors
AffineWarper
    CORRECTED -> 3DForcer
Note: Force Z to 0
3DForcer
    KEEPZVAL = No
    ZVALATTR = 0
    -> CoordinateConcatenator_2
Note: Extract ground coordinate list
CoordinateConcatenator_2
    COORDINATES_TO_INCLUDE_DIS = X Y Z
    COORD_ATTR = _ground
    COORD_DELIM = ;
    ELEMENT_DELIM = " "
    COORDINATES_TO_INCLUDE = X Y Z
    -> AttributeSplitter_3
Note: Split ground coordinate list
AttributeSplitter_3
    ATTR_NAME = _ground
    DELIMITER = ;
    DROP_EMPTY_PARTS = No
    LIST_NAME = _ground
    TRIM_COMMAND = trim
    TRIM_OPTION = Both
    -> AttributeKeeper_3
Note: Remove unneeded / attributes
AttributeKeeper_3
    KEEP_ATTRS = _join,_ground{0},_ground{1},_ground{2},_ground{3}
    -> FeatureMerger [SUPPLIER]

Bookmark: Clip raster
Note: Clip raster to boundary
Clipper
    BOUNDARY = INSIDE
    DO_NOT_AGGREGATE = NO
    MERGE_ATTRS = No
    MULTI_CLIP = YES
    PRESERVE_CLIPPEE_EXTENTS_LOOKUP = $(PCE)
    BOUNDARY_CASES = Treat as Inside
    CLIP_TYPE = Multiple Clippers
    CREATE_AGGREGATES = Yes
    PRESERVE_CLIPPEE_EXTENTS = $(PCE)
    INSIDE -> AttributeCreator
    CLIPPED_INSIDE -> AttributeCreator_2
    CLIPPED_OUTSIDE -> AttributeCreator_3
    OUTSIDE -> AttributeCreator_4
Note: Store output type
AttributeCreator
    ATTR_LIST = _clip_status,inside,_join,fme_basicstring:27%7:@Value(_RasterGCPClipperID)_inside
    -> Tester_4
AttributeCreator_4
    ATTR_LIST = _clip_status,outside,_join,@Value(_RasterGCPClipperID)_outside
    -> Tester_4
AttributeCreator_2
    ATTR_LIST = _clip_status,clipped_inside,_join,@Value(_RasterGCPClipperID)_clipped_inside
    -> Tester
AttributeCreator_3
    ATTR_LIST = _clip_status,clipped_outside,_join,@Value(_RasterGCPClipperID)_clipped_outside
    -> Tester

Bookmark: Extract new GCP pixel coordinates
Note: Extract clipped bounds
BoundingBoxReplacer_3
    BBTYPE = BB
    BOXTYPE = Bounding Box
    BOX -> Offsetter
Note: Adjust LL to 0,0
Offsetter
    XOFF = 0
    YOFF = @Value(_num_rows)
    ZOFF = 0
    OFFSET -> CoordinateConcatenator_3
Note: Extract pixel coordinate list
CoordinateConcatenator_3
    COORDINATES_TO_INCLUDE_DIS = X Y
    COORD_ATTR = _pixel
    COORD_DELIM = ;
    ELEMENT_DELIM = " "
    COORDINATES_TO_INCLUDE = X Y
    -> AttributeSplitter_4
Note: Split pixel coordinate list
AttributeSplitter_4
    ATTR_NAME = _pixel
    DELIMITER = ;
    DROP_EMPTY_PARTS = No
    LIST_NAME = _pixel
    TRIM_COMMAND = trim
    TRIM_OPTION = Both
    -> AttributeKeeper_2
Note: Remove unneeded / attributes
AttributeKeeper_2
    KEEP_ATTRS = _join,_pixel{0},_pixel{1},_pixel{2},_pixel{3}
    -> FeatureMerger [SUPPLIER]

Bookmark: Create new raster GCPs
Note: Merge new pixel and / ground lists onto raster
FeatureMerger
    BUILD_INCOMPLETE = Yes
    PROCESS_DUPS = Yes
    REFEEATTR = _join
    REFERATTR = _join
    REFERENCE_INFO = ATTRIBUTES
    MERGE_TYPE = Attributes Only
    COMPLETE -> StringConcatenator
Note: Concatenate new GCPs / from pixel and ground lists
StringConcatenator
    PARM_LINE = @Value(_pixel{1}) @Value(_ground{0});@Value(_pixel{0}) @Value(_ground{1});@Value(_pixel{3}) @Value(_ground{2});@Value(_pixel{2}) @Value(_ground{3})
    VAL_ATTR = _new_gcp
    -> AttributeRemover
Note: Remove unneeded attributes
AttributeRemover
    REMOVE_ATTRS = _gcp_value,_join
    -> RasterGCPSetter
Note: Apply new GCPs to raster
RasterGCPSetter
    GCP_VALUE = @Value(_new_gcp)
    SOURCE = &_gcp_coordsys
    -> AttributeFilter

Bookmark: Redirect to output and remove temporary attributes
AttributeFilter
    ATTR_NAME = _clip_status
    ATTR_VALUES = <BLANK>,<UNFILTERED>,inside,clipped_inside,clipped_outside,outside
    inside -> AttributeRemover_2
    clipped_inside -> AttributeRemover_3
    clipped_outside -> AttributeRemover_4
    outside -> AttributeRemover_5
AttributeRemover_2
    LIST_ATTRS = _pixel{} _ground{}
    REMOVE_ATTRS = _RasterGCPClipperID,_gcp_coordsys,_clip_status,_fme_no_clipper,_num_bands,_num_rows,_num_columns,_spacing_x,_spacing_y,_origin_x,_origin_y,_rotation_x,_rotation_y,_min_x,_min_y,_max_x,_max_y,_cell_origin_x,_cell_origin_y,_upper_left_x,_upper_left_y,_upper_right_x,_upper_right_y,_lower_right_x,_lower_right_y,_lower_left_x,_lower_left_y,_pixel{0},_pixel{1},_pixel{2},_pixel{3},_ground{0},_ground{1},_ground{2},_ground{3},_new_gcp,_gcp_value,_join,_copynum
    -> INSIDE (output)
INSIDE (output)
AttributeRemover_3
    LIST_ATTRS = _pixel{} _ground{}
    REMOVE_ATTRS = _RasterGCPClipperID,_gcp_coordsys,_clip_status,_fme_no_clipper,_num_bands,_num_rows,_num_columns,_spacing_x,_spacing_y,_origin_x,_origin_y,_rotation_x,_rotation_y,_min_x,_min_y,_max_x,_max_y,_cell_origin_x,_cell_origin_y,_upper_left_x,_upper_left_y,_upper_right_x,_upper_right_y,_lower_right_x,_lower_right_y,_lower_left_x,_lower_left_y,_pixel{0},_pixel{1},_pixel{2},_pixel{3},_ground{0},_ground{1},_ground{2},_ground{3},_new_gcp,_gcp_value,_join,_copynum
    -> CLIPPED_INSIDE (output)
CLIPPED_INSIDE (output)
AttributeRemover_4
    LIST_ATTRS = _pixel{} _ground{}
    REMOVE_ATTRS = _RasterGCPClipperID,_gcp_coordsys,_clip_status,_fme_no_clipper,_num_bands,_num_rows,_num_columns,_spacing_x,_spacing_y,_origin_x,_origin_y,_rotation_x,_rotation_y,_min_x,_min_y,_max_x,_max_y,_cell_origin_x,_cell_origin_y,_upper_left_x,_upper_left_y,_upper_right_x,_upper_right_y,_lower_right_x,_lower_right_y,_lower_left_x,_lower_left_y,_pixel{0},_pixel{1},_pixel{2},_pixel{3},_ground{0},_ground{1},_ground{2},_ground{3},_new_gcp,_gcp_value,_join,_copynum
    -> CLIPPED_OUTSIDE (output)
AttributeRemover_5
    LIST_ATTRS = _pixel{} _ground{}
    REMOVE_ATTRS = _RasterGCPClipperID,_gcp_coordsys,_clip_status,_fme_no_clipper,_num_bands,_num_rows,_num_columns,_spacing_x,_spacing_y,_origin_x,_origin_y,_rotation_x,_rotation_y,_min_x,_min_y,_max_x,_max_y,_cell_origin_x,_cell_origin_y,_upper_left_x,_upper_left_y,_upper_right_x,_upper_right_y,_lower_right_x,_lower_right_y,_lower_left_x,_lower_left_y,_pixel{0},_pixel{1},_pixel{2},_pixel{3},_ground{0},_ground{1},_ground{2},_ground{3},_new_gcp,_gcp_value,_join,_copynum
    -> OUTSIDE (output)
